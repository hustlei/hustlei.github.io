(defun c:xz(/ p0 zh h pt k xp plist pplist mm mmm i n os grid yy hh opw tt txt txt1 klist kklist)
  (setvar "CMDECHO" 0)
  (setq os (getvar "OSMODE"))
  (setq grid (getvar "GRIDMODE"))
  (setvar "GRIDMODE" 0)
  (setvar "OSMODE" 15359)
  (if (= #p0 nil) (setq #p0 (list 0 0 0)))
  (prompt "\n请选择基线上任一点<")
  (princ #p0)
  (setq p0 (getpoint ">:"))
  (if p0 (setq #p0 p0))
  

  (if (= #zg nil) (setq #zg 40))
  (prompt "\n请输入型值数据字高<")
  (princ #zg)
  (setq zg (getdist ">:"))
  (if zg (setq #zg zg))
  

  (if (= #h nil) (setq #h 100))
  (prompt "\n请输入型值数据间距<")
  (princ #h)
  (setq h (getdist ">:"))
  (if h (setq #h h))
  

  (while (setq pt (getpoint "\n请选择型值点(结束选点请按空格或回车):"))
    (if (= i nil) (setq i 0))
    (if (= plist nil) (setq plist (list (cadr pt))))
    (if (= pplist nil) (setq pplist (list (car pt))))
    (setq pplist (cons (car pt) pplist))
    (setq plist (cons (cadr pt) plist))
    (setq i (1+ i))
    (prompt "<")
    (princ i)
    (prompt ">")
    (princ (rtos (- (car pt) (car #p0)) 2 0)) 
    (prompt ",")
    (princ (rtos (- (cadr pt) (cadr #p0)) 2 0))
    (if (= i 1) (setq plist (list (cadr pt))))
    (if (= i 1) (setq pplist (list (car pt))))
   )

  (setq xp (getpoint "\n请选择型值数据插入的第一点:"))
  
  (setvar "OSMODE" 0)
  
  (repeat i
    (if (= n nil) (setq n i))
    (setq mm (list (car xp) (- (cadr xp) (* (- n 1) #h))))
    (setq mmm (list (+(* 5 #zg) (car xp)) (- (cadr xp) (* (- n 1) #h))))
    (setq txt (rtos (- (car plist) (cadr #p0)) 2 0))
    (setq txt1 (rtos (- (car pplist) (car #p0)) 2 0))
    (if (= klist nil) (setq klist (list txt)))
    (if (= kklist nil) (setq kklist (list txt1)))
    (setq klist (cons txt klist))
    (setq kklist (cons txt1 kklist))
    
    (command "TEXT" mmm #zg "0" txt1 "")
    (command "TEXT" mm #zg "0" txt "")
    (princ)
    (setq plist (cdr plist))
    (setq pplist (cdr pplist))
    (setq n (1- n))
   )
  ;(if (setq yy (getstring "\n请输入要保存的名称:"))
   ; (progn
    ;  (setq hh (strcat "d:/陈辉/" yy ".txt"))
    ; (setq opw (open hh "w"))
    ; (repeat i
    ;   (setq tt (car klist))
    ;   (princ tt opw)
    ;   (princ "\n" opw)
    ;   (setq klist (cdr klist))
    ;   )
    ; )
  ;  )
 ; (close opw)
  (setvar "GRIDMODE" grid)
  (setvar "OSMODE" os)
  (princ)
 )
